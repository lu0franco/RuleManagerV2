'Dim factoryDoc = ThisDoc.FactoryDocument

Sub Main()
iLogicVb.RunExternalRule("D:\Bibliotecas\Ilogic\Reglas\IAM\PropAsignaux.iLogicVb")

' Obtener el ensamblaje activo
Dim partDoc As PartDocument
partDoc = ThisApplication.ActiveDocument
' Crear una lista para almacenar los nombres de los subensamblajes
' Analizar el ensamblaje principal en busca de subensamblajes
Analyze(partDoc)

' Mostrar la cantidad de subensamblajes encontrados y sus nombres
'  MsgBox("Cantidad de subensamblajes encontrados: " & subAssemblyNames.Count & vbCrLf &
' "Nombres de los subensamblajes:" & vbCrLf &
' String.Join(vbCrLf, subAssemblyNames.ToArray()), vbInformation, "Subensamblajes Encontrados")
MsgBox("Se han asignado las propiedades correctamente", vbInformation, "Éxito")
End Sub

Sub Analyze(partDoc As PartDocument)
	' Iterar sobre las ocurrencias del ensamblaje actual



				If not partDoc.IsModifiable Then

					Exit Sub
				End If

			
				' Iterar sobre las piezas y subensamblajes en el subensamblaje actual
					' Crear o establecer propiedades en el subensamblaje
					Dim elemento As Object
					elemento = partDoc

					Dim customProps As PropertySet
					standardProperties = elemento.PropertySets.Item("Design Tracking Properties")
					Try
						customProps = elemento.PropertySets.Item("Inventor User Defined Properties")
					Catch ex As Exception
						customProps = elemento.PropertySets.Add("Inventor User Defined Properties")
					End Try

					' Crear o establecer el valor de la propiedad "MC"
					Dim propMC As [Property]
					propMC = GetOrCreateProperty(customProps, "MC")

					' Crear o establecer el valor de la propiedad "CYP"
					Dim propCYP As [Property]
					propCYP = GetOrCreateProperty(customProps, "CYP")

					' Crear o establecer el valor de la propiedad "MEC"
					Dim propMEC As [Property]
					propMEC = GetOrCreateProperty(customProps, "MEC")

					' Crear o establecer el valor de la propiedad "ARM"
					Dim propARM As [Property]
					propARM = GetOrCreateProperty(customProps, "ARM")

					' Asignar las propiedades al subensamblaje
					ASIGN(propMC, propCYP, propMEC, propARM, elemento)


End Sub





Function ASIGN(propMC As [Property], propCYP As [Property], propMEC As [Property], propARM As [Property], elemento As PartDocument)
	' Verificar si la propiedad "COM" no es nula antes de asignar otras propiedades
	Dim customProps As PropertySet
	Dim standardProperties As PropertySet
	standardProperties = elemento.PropertySets.Item("Design Tracking Properties")
	Try

		customProps = elemento.PropertySets.Item("Inventor User Defined Properties")
		Dim propCOM As [Property] = customProps.Item("COM")
		If propCOM.Value = "✓" Then
			' Si el valor de "COM" no es nulo, borrar las otras propiedades
			Try
				customProps.Item("MC").Delete()
			Catch ex As Exception
			End Try
			Try
				customProps.Item("CYP").Delete()
			Catch ex As Exception
			End Try
			Try
				customProps.Item("ARM").Delete()
			Catch ex As Exception
			End Try
			Try
				customProps.Item("MEC").Delete()
			Catch ex As Exception
			End Try
			Dim propLARGO As [Property]
			totalLengthstr = CalculateTotalLength(elemento)
			propLARGO = GetOrCreateProperty(customProps, "LARGO")
			propLARGO.Value = totalLengthstr
			Dim propANCHO As [Property]
			totalWidthstr = CalculateTotalWidth(elemento)
			propANCHO = GetOrCreateProperty(customProps, "ANCHO")
			propANCHO.Value = totalWidthstr
			'MsgBox(standardProperties.Item("Part Number").Value)
			Exit Function
		End If
	Catch ex As Exception
		' La propiedad "COM" no existe en esta ocurrencia
	End Try
	MsgBox(elemento.SubType)
	Select Case elemento.SubType
		

		Case "{9C464203-9BAE-11D3-8BAD-0060B0CE6BB4}" ' CODIGO PIEZA CHAPA
			propMC.Value = "✓"

			Dim oSheetMetalCompDef As SheetMetalComponentDefinition = elemento.ComponentDefinition
			If Not oSheetMetalCompDef.HasFlatPattern Then
				' Crear un nuevo desarrollo plano
				'MsgBox(elemento.Name & "no tiene desarrollo")
				Try
					oSheetMetalCompDef.Unfold
				Catch ex1 As Exception
					MsgBox(elemento.Name & "error")
				End Try


			End If

			Dim propMAT_PLANO As [Property]
			propMAT_PLANO = GetOrCreateProperty(customProps, "MATERIAL_PLANO")
			If propMAT_PLANO.Value = " " Then
				propMAT_PLANO.Value = standardProperties.Item("Material").Value
			End If
			Dim propLARGO As [Property]
			propLARGO = GetOrCreateProperty(customProps, "LARGO")
			propLARGO.Value = "=<Flat Pattern Length>"'"=<SHEET METAL LENGTH>"
			Dim doubleValue As Double = CDbl(propLARGO.Value) * 10
			doubleValue = Round(doubleValue, 0)
			'MsgBox(doubleValue)
			propLARGO.Value = CStr(doubleValue) & " mm"
			Dim propANCHO As [Property]
			propANCHO = GetOrCreateProperty(customProps, "ANCHO")
			propANCHO.Value = "=<Flat Pattern Width>"'"=<SHEET METAL WIDTH>"
			doubleValue = CDbl(propANCHO.Value) * 10
			doubleValue = Round(doubleValue, 0)
			'MsgBox(doubleValue)
			propANCHO.Value = CStr(doubleValue) & " mm"
			If oSheetMetalCompDef.FlatPattern IsNot Nothing AndAlso oSheetMetalCompDef.FlatPattern.FlatBendResults IsNot Nothing Then
				Dim numPatrones As Integer = oSheetMetalCompDef.FlatPattern.FlatBendResults.Count
				Dim numPliegues As Integer = numPatrones / 2
				' Asignar el valor según la condición para "CHAPA" y "PLIEGUE"
				If numPliegues > 0 Then
					propCYP.Value = "✓"
					'MsgBox("CYP")
				End If
			End If
			standardProperties.Item("Project").Value = SharedVariable("descripcion")
			standardProperties.Item("Vendor").Value = SharedVariable("Cliente")
			Dim propESPESOR As [Property]
			propESPESOR = GetOrCreateProperty(customProps, "ESPESOR")
			propESPESOR.Value = (oSheetMetalCompDef.Thickness.Value) * 10
		Case 83886592 'CODIGO PIEZA NORMALIZADA
			propMEC.Value = "✓"
			Try

				If elemento.PropertySets.Item("Inventor User Defined Properties").Item("PERFILERIA").Value = "✓" Then
					propMEC.Value = ""
				End If

			Catch
			End Try
			Dim propMAT_PLANO As [Property]
			propMAT_PLANO = GetOrCreateProperty(customProps, "MATERIAL_PLANO")
			If propMAT_PLANO.Value = " " Then
				propMAT_PLANO.Value = standardProperties.Item("Material").Value
			End If
			Dim propLARGO As [Property]
			totalLengthstr = CalculateTotalLength(elemento)
			propLARGO = GetOrCreateProperty(customProps, "LARGO")
			propLARGO.Value = totalLengthstr
			Dim propANCHO As [Property]
			totalWidthstr = CalculateTotalWidth(elemento)
			propANCHO = GetOrCreateProperty(customProps, "ANCHO")
			propANCHO.Value = totalWidthstr
			standardProperties.Item("Project").Value = SharedVariable("descripcion")
			standardProperties.Item("Vendor").Value = SharedVariable("Cliente")
			'MsgBox("MEC")
	End Select
End Function


Function GetOrCreateProperty(props As Inventor.PropertySet, propName As String) As Inventor.Property
	Dim prop As Inventor.Property
	' Verificar si la propiedad ya existe
	For Each prop In props
		If prop.Name = propName Then
			Return prop ' Devolver la propiedad existente
		End If
	Next

	' Crear la propiedad si no existe
	Return props.Add(" ", propName)
End Function

Function CalculateTotalLength(elemento As ComponentOccurrence) As String


	' Obtener la caja delimitadora que engloba todos los cuerpos de la pieza
	Dim cajaDelimitadora As Box
	cajaDelimitadora = elemento.ComponentDefinition.PreciseRangeBox
	Dim Xlength As Double = (cajaDelimitadora.MaxPoint.X - cajaDelimitadora.MinPoint.X) * 10
	Dim Ylength As Double = (cajaDelimitadora.MaxPoint.Y - cajaDelimitadora.MinPoint.Y) * 10
	Dim Zlength As Double = (cajaDelimitadora.MaxPoint.Z - cajaDelimitadora.MinPoint.Z) * 10
	Dim totalLength As Double
	' Desestimar las variables iguales a la variable de mayor longitud
	If Xlength = Ylength Then
		Xlength = 0
		Ylength = 0
	ElseIf Xlength = Zlength Then
		Xlength = 0
		Zlength = 0
	ElseIf Ylength = Zlength Then
		Ylength = 0
		Zlength = 0
	End If
	If Xlength > Ylength And Xlength > Zlength Then
		totalLength = Xlength
	ElseIf Ylength > Xlength And Ylength > Zlength Then
		totalLength = Ylength
	Else
		totalLength = Zlength
	End If

	totalLength = Math.Round(totalLength)
	'If propMEC.Value = "✓" Then
	Try
		'MsgBox(partDoc.PropertySets.Item("Inventor User Defined Properties").Item("MEC").Value)
		If elemento.PropertySets.Item("Inventor User Defined Properties").Item("MEC").Value = "✓" Then
			'If propMEC.Value = "✓" Then
			'totalLength = totalLength + 3
		End If
	Catch
	End Try

	' Convertir el totalLength a una cadena y agregar "mm"
	Dim totalLengthStr As String = totalLength.ToString() & " mm"
	Return totalLengthStr
End Function

Function CalculateTotalWidth(elemento As ComponentOccurrence) As String



	' Obtener la caja delimitadora que engloba todos los cuerpos de la pieza
	Dim cajaDelimitadora As Box
	cajaDelimitadora = elemento.ComponentDefinition.PreciseRangeBox
	Dim XWidth As Double = (cajaDelimitadora.MaxPoint.X - cajaDelimitadora.MinPoint.X) * 10
	Dim YWidth As Double = (cajaDelimitadora.MaxPoint.Y - cajaDelimitadora.MinPoint.Y) * 10
	Dim ZWidth As Double = (cajaDelimitadora.MaxPoint.Z - cajaDelimitadora.MinPoint.Z) * 10
	Dim totalWidth As Double
	' Encontrar el segundo número de mayor valor
	If (XWidth >= YWidth And XWidth <= ZWidth) Or (XWidth <= YWidth And XWidth >= ZWidth) Then
		totalWidth = XWidth
	ElseIf (YWidth >= XWidth And YWidth <= ZWidth) Or (YWidth <= XWidth And YWidth >= ZWidth) Then
		totalWidth = YWidth
	Else
		totalWidth = ZWidth
	End If
	totalWidth = Math.Round(totalWidth)
	' Convertir las longitudes a cadenas y agregar "mm"
	Dim totalWidthStr As String = totalWidth.ToString() & " mm"

	Return totalWidthStr
End Function

Function CalculateMinWidth(elemento As ComponentOccurrence) As String

	' Obtener la caja delimitadora que engloba todos los cuerpos de la pieza
	Dim cajaDelimitadora As Box
	cajaDelimitadora = elemento.ComponentDefinition.PreciseRangeBox
	Dim XWidth As Double = (cajaDelimitadora.MaxPoint.X - cajaDelimitadora.MinPoint.X) * 10
	Dim YWidth As Double = (cajaDelimitadora.MaxPoint.Y - cajaDelimitadora.MinPoint.Y) * 10
	Dim ZWidth As Double = (cajaDelimitadora.MaxPoint.Z - cajaDelimitadora.MinPoint.Z) * 10

	' Encontrar el número más pequeño de los tres
	Dim minWidth As Double = Math.Min(XWidth, Math.Min(YWidth, ZWidth))

	' Redondear el resultado
	minWidth = Math.Round(minWidth)

	' Convertir la longitud a cadena y agregar "mm"
	Dim minWidthStr As String = minWidth.ToString() & " mm"

	Return minWidthStr
End Function
