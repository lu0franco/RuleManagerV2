AddReference "Microsoft.Office.Interop.Excel"
    Imports Excel = Microsoft.Office.Interop.Excel
'=============================
' EXPORTAR BOM A EXCEL (ODOO)
'=============================


Sub Main()

    ExportBOMFiltrada()
    MessageBox.Show("BOM exportada lista para Odoo 😎")

End Sub


'=============================
' EXPORTADOR PRINCIPAL
'=============================
Sub ExportBOMFiltrada()

    Dim oAsmDoc As AssemblyDocument = ThisApplication.ActiveDocument
    Dim oBOM As BOM = oAsmDoc.ComponentDefinition.BOM

    oBOM.PartsOnlyViewEnabled = True
    Dim oView As BOMView = oBOM.BOMViews.Item("Solo piezas")

    ' Excel
    Dim oExcel As Excel.Application = New Excel.Application
    oExcel.Visible = True

    Dim oBook As Excel.Workbook = oExcel.Workbooks.Add()
    Dim oSheet As Excel.Worksheet = oBook.Sheets(1)

    '-----------------------------
    ' ENCABEZADOS
    '-----------------------------
    oSheet.Cells(1, 1).Value = "External ID"
    oSheet.Cells(1, 2).Value = "Reference"
    oSheet.Cells(1, 3).Value = "Product"
    oSheet.Cells(1, 4).Value = "Quantity"
    oSheet.Cells(1, 5).Value = "BoM Type"
    oSheet.Cells(1, 6).Value = "BoM Lines/Component"
    oSheet.Cells(1, 7).Value = "BoM Lines/Quantity"

    '-----------------------------
    ' PROPIEDADES ENSAMBLE
    '-----------------------------
    Dim proyecto As String = iProperties.Value("Project", "Project")
    Dim nroAlmacen As String = iProperties.Value("Project", "Stock Number")
    Dim nroPieza As String = iProperties.Value("Design Tracking Properties", "Part Number")

    ' FILA 2 (KIT)
    oSheet.Cells(2, 1).Value = proyecto
    oSheet.Cells(2, 2).Value = nroAlmacen
    oSheet.Cells(2, 3).Value = nroPieza & " - " & proyecto
    oSheet.Cells(2, 4).Value = 1
    oSheet.Cells(2, 5).Value = "Kit"

    '-----------------------------
    ' DICCIONARIO (FUSIÓN)
    '-----------------------------
    Dim dict As Object
    dict = CreateObject("Scripting.Dictionary")

    '-----------------------------
    ' RECORRER BOM
    '-----------------------------
    For Each oRow As BOMRow In oView.BOMRows

    Dim oCompDef As ComponentDefinition = oRow.ComponentDefinitions.Item(1)
    Dim oDoc As Document = oCompDef.Document

    Dim esCOM As Boolean = TieneMarca(oDoc, "COM")
    Dim esBuloneria As Boolean = TieneMarca(oDoc, "BULONERIA")

    If esCOM Or esBuloneria Then

        Dim partNumber As String = ""
        Dim refAlmacen As String = ""
        Dim fileName As String = System.IO.Path.GetFileName(oDoc.FullFileName)

    
            partNumber = oDoc.PropertySets.Item("Design Tracking Properties").Item("Part Number").Value

            refAlmacen = oDoc.PropertySets.Item("Design Tracking Properties").Item("Stock Number").Value

        If refAlmacen = "" Then 
			refAlmacen=partNumber
		End If

        Dim cantidad As Integer = oRow.ItemQuantity

        ' 🔑 CLAVE COMPUESTA
        Dim clave As String = partNumber & "|" & refAlmacen

        If dict.Exists(clave) Then

            Dim item As ItemBOM = dict(clave)
            item.Qty += cantidad

            ' Guardar nombre de archivo si es nuevo
            If Not item.Files.Contains(fileName) Then
                item.Files.Add(fileName)
            End If

        Else

            Dim item As New ItemBOM
            item.Ref = refAlmacen
            item.Qty = cantidad
            item.Files.Add(fileName)

            dict.Add(clave, item)

        End If

    End If

Next

    '-----------------------------
    ' ESCRIBIR EN EXCEL
    '-----------------------------
    Dim rowExcel As Integer = 1


For Each key As Object In dict.Keys
rowExcel += 1
    Dim item As ItemBOM = dict(key)

    ' Si hay más de un archivo distinto → caso SAT
    If item.Files.Count > 1 Then

        Dim msg As String = "Se detectaron múltiples archivos con mismo código:" & vbCrLf & vbCrLf & _
                           "Archivos:" & vbCrLf & String.Join(vbCrLf, item.Files.ToArray()) & vbCrLf & vbCrLf & _
                           "Cantidad total detectada: " & item.Qty & vbCrLf & vbCrLf & _
                           "¿Querés usar esta cantidad?"

        Dim resp = MessageBox.Show(msg, "Validación requerida", MessageBoxButtons.YesNo)

        If resp = DialogResult.No Then

            Dim inputQty As String = InputBox("Ingresá la cantidad correcta:", "Corrección manual", item.Qty)

            If IsNumeric(inputQty) Then
                item.Qty = CInt(inputQty)
            End If

        End If

    End If
	oSheet.Cells(rowExcel, 6).Value = item.Ref 
	oSheet.Cells(rowExcel, 7).Value = item.Qty

Next

    oSheet.Columns.AutoFit()

End Sub


'=============================
' CLASE PARA AGRUPAR
'=============================
Class ItemBOM
    Public Ref As String
    Public Qty As Integer
    Public Files As New List(Of String)
End Class


'=============================
' VERIFICAR ✓ EN PROPIEDAD
'=============================
Function TieneMarca(oDoc As Document, propName As String) As Boolean

    Try
        Dim customProps As PropertySet
        customProps = oDoc.PropertySets.Item("Inventor User Defined Properties")

        Dim val As String = customProps.Item(propName).Value

        If val = "✓" Then Return True

    Catch
    End Try

    Return False

End Function
