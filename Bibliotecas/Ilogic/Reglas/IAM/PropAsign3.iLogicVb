Imports System
Imports System.Collections.Generic
Imports Inventor
'Dim factoryDoc = ThisDoc.FactoryDocument

Sub Main()
SharedVariable("DictConsultasMEC") = New Dictionary(Of String, Boolean)(StringComparer.OrdinalIgnoreCase)
iLogicVb.RunExternalRule("D:\Bibliotecas\Ilogic\Reglas\IAM\PropAsignaux.iLogicVb")

' Obtener el ensamblaje activo
Dim assemblyDoc As AssemblyDocument
assemblyDoc = ThisApplication.ActiveDocument
' Crear una lista para almacenar los nombres de los subensamblajes
Dim subAssemblyNames As New List(Of String)
' Analizar el ensamblaje principal en busca de subensamblajes
AnalyzeSubAssemblies(assemblyDoc.ComponentDefinition, subAssemblyNames)

' Mostrar la cantidad de subensamblajes encontrados y sus nombres
'  MsgBox("Cantidad de subensamblajes encontrados: " & subAssemblyNames.Count & vbCrLf &
' "Nombres de los subensamblajes:" & vbCrLf &
' String.Join(vbCrLf, subAssemblyNames.ToArray()), vbInformation, "Subensamblajes Encontrados")
MsgBox("Se han asignado las propiedades correctamente", vbInformation, "Éxito")
End Sub

Sub AnalyzeSubAssemblies(compDef As ComponentDefinition, ByRef subAssemblyNames As List(Of String))
	' Iterar sobre las ocurrencias del ensamblaje actual
	Dim oProgressStep As Integer = 0
	For Each oOcc As ComponentOccurrence In compDef.Occurrences
		' Verificar si la ocurrencia está activa
		If Not oOcc.Suppressed Then
			If Not oOcc.Visible  Then
				'MsgBox(oOcc.Name & "No se analizará por estar oculta")
				Continue For
			End If
			If oOcc.BOMStructure = BOMStructureEnum.kReferenceBOMStructure Then
				'MsgBox(oOcc.Name & "No se analizará por ser una referencia")
				Continue For
			End If
			If oOcc.DefinitionDocumentType = kPartDocumentObject Then
				If oOcc.Definition.IsContentMember Then

					Continue For
				End If

			End If
			' Verificar si la ocurrencia es un subensamblaje
			If oOcc.DefinitionDocumentType = kAssemblyDocumentObject Then
				' Guardar el nombre del subensamblaje
				subAssemblyNames.Add(oOcc.Name)

				' Obtener el conjunto de definición del subensamblaje
				Dim subAssemblyCompDef As AssemblyComponentDefinition
				Try
					subAssemblyCompDef = oOcc.Definition
				Catch ex As Exception
					MsgBox("error con" & oOcc.Name)
				End Try
				oProgressStep = oProgressStep + 1
				Dim oProgressBar As Inventor.ProgressBar
				Dim oProgressSteps As Integer = compDef.Occurrences.Count
				oProgressStaticText = "Procesando "
				oProgressBar = ThisApplication.CreateProgressBar(True, oProgressSteps, "Progreso")'Big Progress Bar, use True for small
				oProgressBar.Message = (oProgressStaticText & oProgressStep & " de " & oProgressSteps & oOcc.Name)
				oProgressBar.UpdateProgress
				' Iterar sobre las piezas y subensamblajes en el subensamblaje actual
				For Each subOcc As ComponentOccurrence In subAssemblyCompDef.Occurrences
					' Crear o establecer propiedades en el subensamblaje
					Dim elemento As Object
					elemento = oOcc

					Dim customProps As PropertySet
					standardProperties = elemento.Definition.Document.PropertySets.Item("Design Tracking Properties")
					Try
						customProps = elemento.Definition.Document.PropertySets.Item("Inventor User Defined Properties")
					Catch ex As Exception
						customProps = elemento.Definition.Document.PropertySets.Add("Inventor User Defined Properties")
					End Try

					' Crear o establecer el valor de la propiedad "MC"
					Dim propMC As [Property]
					propMC = GetOrCreateProperty(customProps, "MC", elemento)

					' Crear o establecer el valor de la propiedad "CYP"
					Dim propCYP As [Property]
					propCYP = GetOrCreateProperty(customProps, "CYP", elemento)

					' Crear o establecer el valor de la propiedad "MEC"
					Dim propMEC As [Property]
					propMEC = GetOrCreateProperty(customProps, "MEC", elemento)

					' Crear o establecer el valor de la propiedad "ARM"
					Dim propARM As [Property]
					propARM = GetOrCreateProperty(customProps, "ARM", elemento)

					' Asignar las propiedades al subensamblaje
					ASIGN(propMC, propCYP, propMEC, propARM, elemento)
				Next

				' Analizar el subensamblaje en busca de más subensamblajes
				AnalyzeSubAssemblies(subAssemblyCompDef, subAssemblyNames)
			Else
				' Crear o establecer propiedades en el subensamblaje
				Dim elemento As Object
				elemento = oOcc
				Dim customProps As PropertySet
				Try
					customProps = elemento.Definition.Document.PropertySets.Item("Inventor User Defined Properties")
				Catch ex As Exception
					customProps = elemento.Definition.Document.PropertySets.Add("Inventor User Defined Properties")
				End Try

				' Crear o establecer el valor de la propiedad "MC"
				Dim propMC As [Property]
				propMC = GetOrCreateProperty(customProps, "MC", elemento)

				' Crear o establecer el valor de la propiedad "CYP"
				Dim propCYP As [Property]
				propCYP = GetOrCreateProperty(customProps, "CYP", elemento)

				' Crear o establecer el valor de la propiedad "MEC"
				Dim propMEC As [Property]
				propMEC = GetOrCreateProperty(customProps, "MEC", elemento)

				' Crear o establecer el valor de la propiedad "ARM"
				Dim propARM As [Property]
				propARM = GetOrCreateProperty(customProps, "ARM", elemento)

				' Asignar las propiedades al subensamblaje
				ASIGN(propMC, propCYP, propMEC, propARM, elemento)
			End If
		End If
	Next
End Sub





Function ASIGN(propMC As [Property], propCYP As [Property], propMEC As [Property], propARM As [Property], elemento As ComponentOccurrence)
	' Verificar si la propiedad "COM" no es nula antes de asignar otras propiedades
	Dim customProps As PropertySet
	Dim standardProperties As PropertySet
	standardProperties = elemento.Definition.Document.PropertySets.Item("Design Tracking Properties")
	Try

		customProps = elemento.Definition.Document.PropertySets.Item("Inventor User Defined Properties")
		Dim propCOM As [Property] = customProps.Item("COM")
		If propCOM.Value = "✓" Then
			' Si el valor de "COM" no es nulo, borrar las otras propiedades
			Try
				customProps.Item("MC").Delete()
			Catch ex As Exception
			End Try
			Try
				customProps.Item("CYP").Delete()
			Catch ex As Exception
			End Try
			Try
				customProps.Item("ARM").Delete()
			Catch ex As Exception
			End Try
			Try
				customProps.Item("MEC").Delete()
			Catch ex As Exception
			End Try
			Dim propLARGO As [Property]
			totalLengthstr = CalculateTotalLength(elemento)
			propLARGO = GetOrCreateProperty(customProps, "LARGO",elemento)
			propLARGO.Value = totalLengthstr
			Dim propANCHO As [Property]
			totalWidthstr = CalculateTotalWidth(elemento)
			propANCHO = GetOrCreateProperty(customProps, "ANCHO",elemento)
			propANCHO.Value = totalWidthstr
			'MsgBox(standardProperties.Item("Part Number").Value)
			Exit Function
		End If
	Catch ex As Exception
		' La propiedad "COM" no existe en esta ocurrencia
	End Try
	'MsgBox(elemento.Name)
	Select Case elemento.Definition.Type
		Case 100663808 ' CODIGO IAM
			propARM.Value = "✓"
			Dim propLARGO As [Property]
			totalLengthstr = CalculateTotalLength(elemento)
			propLARGO = GetOrCreateProperty(customProps, "LARGO",elemento)
			propLARGO.Value = totalLengthstr
			Dim propANCHO As [Property]
			totalWidthstr = CalculateTotalWidth(elemento)
			propANCHO = GetOrCreateProperty(customProps, "ANCHO",elemento)
			propANCHO.Value = totalWidthstr

			standardProperties.Item("Project").Value = SharedVariable("descripcion")
			standardProperties.Item("Vendor").Value = SharedVariable("Cliente")
			'MsgBox("ARM")
			' Crear una lista para almacenar las piezas del árbol de diseño

		Case 150995200 ' CODIGO PIEZA CHAPA
			propMC.Value = "✓"

			Dim oSheetMetalCompDef As SheetMetalComponentDefinition = elemento.Definition
			If Not oSheetMetalCompDef.HasFlatPattern Then
				' Crear un nuevo desarrollo plano
				'MsgBox(elemento.Name & "no tiene desarrollo")
				Try
					oSheetMetalCompDef.Unfold
				Catch ex1 As Exception
					MsgBox(elemento.Name & "error")
				End Try


			End If

			Dim propMAT_PLANO As [Property]
			propMAT_PLANO = GetOrCreateProperty(customProps, "MATERIAL_PLANO",elemento)
			If propMAT_PLANO.Value = " " Then
				propMAT_PLANO.Value = standardProperties.Item("Material").Value
			End If
			Dim propLARGO As [Property]
			propLARGO = GetOrCreateProperty(customProps, "LARGO",elemento)
			propLARGO.Value = "=<Flat Pattern Length>"'"=<SHEET METAL LENGTH>"
			Dim doubleValue As Double = CDbl(propLARGO.Value) * 10
			doubleValue = Round(doubleValue, 0)
			'MsgBox(doubleValue)
			propLARGO.Value = CStr(doubleValue) & " mm"
			Dim propANCHO As [Property]
			propANCHO = GetOrCreateProperty(customProps, "ANCHO",elemento)
			propANCHO.Value = "=<Flat Pattern Width>"'"=<SHEET METAL WIDTH>"
			doubleValue = CDbl(propANCHO.Value) * 10
			doubleValue = Round(doubleValue, 0)
			'MsgBox(doubleValue)
			propANCHO.Value = CStr(doubleValue) & " mm"
			If oSheetMetalCompDef.FlatPattern IsNot Nothing AndAlso oSheetMetalCompDef.FlatPattern.FlatBendResults IsNot Nothing Then
				Dim numPatrones As Integer = oSheetMetalCompDef.FlatPattern.FlatBendResults.Count
				Dim numPliegues As Integer = numPatrones / 2
				' Asignar el valor según la condición para "CHAPA" y "PLIEGUE"
				If numPliegues > 0 Then
					propCYP.Value = "✓"
					'MsgBox("CYP")
				End If
			End If
			standardProperties.Item("Project").Value = SharedVariable("descripcion")
			standardProperties.Item("Vendor").Value = SharedVariable("Cliente")
			Dim propESPESOR As [Property]
			propESPESOR = GetOrCreateProperty(customProps, "ESPESOR",elemento)
			propESPESOR.Value = (oSheetMetalCompDef.Thickness.Value) * 10
		Case 83886592 'CODIGO PIEZA NORMALIZADA
			propMEC.Value = "✓"
			Try

				If elemento.Definition.Document.PropertySets.Item("Inventor User Defined Properties").Item("PERFILERIA").Value = "✓" Then
					propMEC.Value = ""
				End If

			Catch
			End Try
			Dim propMAT_PLANO As [Property]
			propMAT_PLANO = GetOrCreateProperty(customProps, "MATERIAL_PLANO",elemento)
			If propMAT_PLANO.Value = " " Then
				propMAT_PLANO.Value = standardProperties.Item("Material").Value
			End If
			Dim propLARGO As [Property]
			totalLengthstr = CalculateTotalLength(elemento)
			propLARGO = GetOrCreateProperty(customProps, "LARGO",elemento)
			propLARGO.Value = totalLengthstr
			Dim propANCHO As [Property]
			totalWidthstr = CalculateTotalWidth(elemento)
			propANCHO = GetOrCreateProperty(customProps, "ANCHO",elemento)
			propANCHO.Value = totalWidthstr
			standardProperties.Item("Project").Value = SharedVariable("descripcion")
			standardProperties.Item("Vendor").Value = SharedVariable("Cliente")

			' Si la propiedad MEC tiene el valor "✓", mostrar ventana y consultar sobremedida (+3mm)
			If propMEC.Value = "✓" Then
				Dim docPath As String = ""
				Try
					docPath = elemento.Definition.Document.FullFileName
				Catch
					docPath = elemento.Name
				End Try

				Dim dictMEC As Dictionary(Of String, Boolean) = SharedVariable("DictConsultasMEC")
				If dictMEC Is Nothing Then
					dictMEC = New Dictionary(Of String, Boolean)(StringComparer.OrdinalIgnoreCase)
					SharedVariable("DictConsultasMEC") = dictMEC
				End If

				If Not dictMEC.ContainsKey(docPath) Then
					dictMEC.Add(docPath, True)

					Dim sPartNumber As String = ""
					Try
						sPartNumber = CStr(standardProperties.Item("Part Number").Value)
					Catch
						sPartNumber = elemento.Name
					End Try

					Dim sStockNumber As String = ""
					Try
						sStockNumber = CStr(standardProperties.Item("Stock Number").Value)
					Catch
					End Try
					If String.IsNullOrEmpty(sStockNumber) Then
						Try
							sStockNumber = CStr(customProps.Item("Stock Number").Value)
						Catch
						End Try
					End If

					Dim sMatPlano As String = ""
					Try
						sMatPlano = CStr(propMAT_PLANO.Value)
					Catch
					End Try

					Dim sMensaje As String = "Componente MECANIZADO (MEC):" & vbCrLf & vbCrLf & _
						"• Part Number: " & sPartNumber & vbCrLf & _
						"• Stock Number: " & sStockNumber & vbCrLf & _
						"• Material Plano: " & sMatPlano & vbCrLf & _
						"• Largo: " & totalLengthstr & vbCrLf & _
						"• Ancho: " & totalWidthstr & vbCrLf & vbCrLf & _
						"¿Desea sumarle +3mm al Largo?"

					Dim respuesta As Integer = MsgBox(sMensaje, vbYesNo + vbQuestion, "MEC - " & sPartNumber)
					If respuesta = vbYes Then
						Dim numLargo As Double = 0
						Dim strLimpio As String = totalLengthstr.Replace("mm", "").Trim()
						If Double.TryParse(strLimpio, numLargo) Then
							numLargo = numLargo + 3
							totalLengthstr = numLargo.ToString() & " mm"
						Else
							Try
								numLargo = CDbl(strLimpio) + 3
								totalLengthstr = numLargo.ToString() & " mm"
							Catch
							End Try
						End If
						propLARGO.Value = totalLengthstr
					End If
				End If
			End If
	End Select
End Function


Function GetOrCreateProperty(props As Inventor.PropertySet, propName As String, oOcc As ComponentOccurrence ) As Inventor.Property
	Dim prop As Inventor.Property
	' Verificar si la propiedad ya existe
	For Each prop In props
		If prop.Name = propName Then
			Return prop ' Devolver la propiedad existente
		End If
	Next
	Try
		' Crear la propiedad si no existe
		Return props.Add(" ", propName)
	Catch ex As Exception
		MsgBox("error con" & oOcc.Name & "propiedad: " &propName )
	End Try
End Function

Function CalculateTotalLength(elemento As ComponentOccurrence) As String


	' Obtener la caja delimitadora que engloba todos los cuerpos de la pieza
	Dim cajaDelimitadora As Box
	cajaDelimitadora = elemento.Definition.Document.ComponentDefinition.PreciseRangeBox
	Dim Xlength As Double = (cajaDelimitadora.MaxPoint.X - cajaDelimitadora.MinPoint.X) * 10
	Dim Ylength As Double = (cajaDelimitadora.MaxPoint.Y - cajaDelimitadora.MinPoint.Y) * 10
	Dim Zlength As Double = (cajaDelimitadora.MaxPoint.Z - cajaDelimitadora.MinPoint.Z) * 10
	Dim totalLength As Double
	' Desestimar las variables iguales a la variable de mayor longitud
	If Xlength = Ylength Then
		Xlength = 0
		Ylength = 0
	ElseIf Xlength = Zlength Then
		Xlength = 0
		Zlength = 0
	ElseIf Ylength = Zlength Then
		Ylength = 0
		Zlength = 0
	End If
	If Xlength > Ylength And Xlength > Zlength Then
		totalLength = Xlength
	ElseIf Ylength > Xlength And Ylength > Zlength Then
		totalLength = Ylength
	Else
		totalLength = Zlength
	End If

	totalLength = Math.Round(totalLength)

	' Convertir el totalLength a una cadena y agregar "mm"
	Dim totalLengthStr As String = totalLength.ToString() & " mm"
	Return totalLengthStr
End Function

Function CalculateTotalWidth(elemento As ComponentOccurrence) As String



	' Obtener la caja delimitadora que engloba todos los cuerpos de la pieza
	Dim cajaDelimitadora As Box
	cajaDelimitadora = elemento.Definition.Document.ComponentDefinition.PreciseRangeBox
	Dim XWidth As Double = (cajaDelimitadora.MaxPoint.X - cajaDelimitadora.MinPoint.X) * 10
	Dim YWidth As Double = (cajaDelimitadora.MaxPoint.Y - cajaDelimitadora.MinPoint.Y) * 10
	Dim ZWidth As Double = (cajaDelimitadora.MaxPoint.Z - cajaDelimitadora.MinPoint.Z) * 10
	Dim totalWidth As Double
	' Encontrar el segundo número de mayor valor
	If (XWidth >= YWidth And XWidth <= ZWidth) Or (XWidth <= YWidth And XWidth >= ZWidth) Then
		totalWidth = XWidth
	ElseIf (YWidth >= XWidth And YWidth <= ZWidth) Or (YWidth <= XWidth And YWidth >= ZWidth) Then
		totalWidth = YWidth
	Else
		totalWidth = ZWidth
	End If
	totalWidth = Math.Round(totalWidth)
	' Convertir las longitudes a cadenas y agregar "mm"
	Dim totalWidthStr As String = totalWidth.ToString() & " mm"

	Return totalWidthStr
End Function

Function CalculateMinWidth(elemento As ComponentOccurrence) As String

	' Obtener la caja delimitadora que engloba todos los cuerpos de la pieza
	Dim cajaDelimitadora As Box
	cajaDelimitadora = elemento.Definition.Document.ComponentDefinition.PreciseRangeBox
	Dim XWidth As Double = (cajaDelimitadora.MaxPoint.X - cajaDelimitadora.MinPoint.X) * 10
	Dim YWidth As Double = (cajaDelimitadora.MaxPoint.Y - cajaDelimitadora.MinPoint.Y) * 10
	Dim ZWidth As Double = (cajaDelimitadora.MaxPoint.Z - cajaDelimitadora.MinPoint.Z) * 10

	' Encontrar el número más pequeño de los tres
	Dim minWidth As Double = Math.Min(XWidth, Math.Min(YWidth, ZWidth))

	' Redondear el resultado
	minWidth = Math.Round(minWidth)

	' Convertir la longitud a cadena y agregar "mm"
	Dim minWidthStr As String = minWidth.ToString() & " mm"

	Return minWidthStr
End Function
